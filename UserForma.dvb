Attribute VB_Name = "UserForm1"
Attribute VB_Base = "0{E4E951E4-78C8-4BF4-B533-F7D487EFE991}{23FFB20D-B3FB-409F-B5EB-EFB8E4CC5F41}"
Attribute VB_GlobalNameSpace = False
Attribute VB_Creatable = False
Attribute VB_PredeclaredId = True
Attribute VB_Exposed = False
Attribute VB_TemplateDerived = False
Attribute VB_Customizable = False
Private Sub CheckBox1_Click()

End Sub

Private Sub Label2_Click()

End Sub

Private Sub Label3_Click()

End Sub

Private Sub Label4_Click()

End Sub

Private Sub Label5_Click()

End Sub

Private Sub Label6_Click()

End Sub

Private Sub OptionButton1_Click()

End Sub

Private Sub SpinButton1_Change()
Me.TextBox4.Value = Me.SpinButton1.Value
End Sub

Private Sub TextBox3_Change()

End Sub

Private Sub TextBox4_Change()

End Sub
