Attribute VB_Name = "UserForm1"
Attribute VB_Base = "0{D4DFAD64-94BC-4CF0-AB75-ACE4970E7352}{2976A328-E7D5-475F-A594-F06190D10294}"
Attribute VB_GlobalNameSpace = False
Attribute VB_Creatable = False
Attribute VB_PredeclaredId = True
Attribute VB_Exposed = False
Attribute VB_TemplateDerived = False
Attribute VB_Customizable = False
Private Sub CommandButton1_Click()

End Sub

Private Sub DIJELI_Click()

REZ.Text = CDbl(A) / CDbl(B)

End Sub

Private Sub Label1_Click()

End Sub

Private Sub MINUS_Click()
REZ.Text = CDbl(A) - CDbl(B)
End Sub

Private Sub PLUS_Click()
REZ.Text = CDbl(A) + CDbl(B)
End Sub

Private Sub TextBox1_Change()

End Sub

Private Sub PUTA_Click()
REZ.Text = CDbl(A) * CDbl(B)
End Sub
