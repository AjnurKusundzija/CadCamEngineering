Attribute VB_Name = "UserForm1"
Attribute VB_Base = "0{18EB3DCE-2F82-47DE-A5BD-2F046515137E}{DD0EAB74-D05B-4426-9E9D-85B346A14AB3}"
Attribute VB_GlobalNameSpace = False
Attribute VB_Creatable = False
Attribute VB_PredeclaredId = True
Attribute VB_Exposed = False
Attribute VB_TemplateDerived = False
Attribute VB_Customizable = False
Private Sub CommandButton1_Click()
Dim sipka As Acad3DSolid
Dim centar(0 To 2) As Double
centar(0) = 0: centar(1) = 0: centar(2) = 0
Dim duzina As Double, sirina As Double, visina As Double
duzina = 10: sirina = 2: visina = 2
Set sipka = ThisDrawing.ModelSpace.AddBox(centar, duzina, sirina, visina)


Dim kugla1 As Acad3DSolid
Dim kugla2 As Acad3DSolid
Dim centar1(0 To 2) As Double
Dim centar2(0 To 2) As Double
Dim r1 As Double, r2 As Double
centar1(0) = 5.5: centar1(1) = 0: centar1(2) = 0
centar2(0) = -5.5: centar2(1) = 0: centar2(2) = 0
r1 = 2.5: r2 = 2.5
Set kugla1 = ThisDrawing.ModelSpace.AddSphere(centar1, r1)
Set kugla2 = ThisDrawing.ModelSpace.AddSphere(centar2, r2)
kugla1.Update
kugla2.Update
sipka.Update
End Sub

Private Sub CommandButton2_Click()
Dim sfera As Acad3DSolid
Dim kocka As Acad3DSolid
Dim centar(0 To 2) As Double
Dim radijus As Double: Dim stranica As Double
centar(0) = 0: centar(1) = 0: centar(2) = 0
radijus = 6
stranica = 10
Set kocka = ThisDrawing.ModelSpace.AddBox(centar, stranica, stranica, stranica)
Set sfera = ThisDrawing.ModelSpace.AddSphere(centar, radijus)
kocka.Update
sfera.Update
Call kocka.Boolean(acSubtraction, sfera)
ThisDrawing.Regen True
End Sub
