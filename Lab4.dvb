Attribute VB_Name = "UserForm1"
Attribute VB_Base = "0{4518D9F0-8C91-4C74-B4ED-0FFA8281CFF3}{C94B5AF2-9003-4965-85CF-61B8D20C1C53}"
Attribute VB_GlobalNameSpace = False
Attribute VB_Creatable = False
Attribute VB_PredeclaredId = True
Attribute VB_Exposed = False
Attribute VB_TemplateDerived = False
Attribute VB_Customizable = False
Private Sub CommandButton1_Click()
Dim duz As AcadLine
Dim tacka1(0 To 2) As Double, tacka2(0 To 2) As Double
tacka1(0) = CDbl(TextBox1.Text)
tacka1(1) = CDbl(TextBox2.Text)
tacka2(0) = CDbl(TextBox3.Text)
tacka2(1) = CDbl(TextBox4.Text)
Set duz = ThisDrawing.ModelSpace.AddLine(tacka1, tacka2)
duz.u

End Sub

Private Sub Label1_Click()

End Sub

Private Sub TextBox1_Change()

End Sub

Attribute VB_Name = "UserForm2"
Attribute VB_Base = "0{DFF20F25-1447-42A2-AAE0-F62C8C108AC1}{41FA4EC7-8671-49A1-8125-55CC06C909BA}"
Attribute VB_GlobalNameSpace = False
Attribute VB_Creatable = False
Attribute VB_PredeclaredId = True
Attribute VB_Exposed = False
Attribute VB_TemplateDerived = False
Attribute VB_Customizable = False
Private Sub CommandButton1_Click()
Dim duz As AcadLWPolyline
Dim tacke(0 To 5) As Double

tacke(0) = 0#
tacke(1) = 0#
tacke(2) = 0#
tacke(3) = CDbl(TextBox1.Text)

tacke(4) = CDbl(TextBox2.Text)
tacke(5) = 0#

Set duz = ThisDrawing.ModelSpace.AddLightWeightPolyline(tacke)

If Not duz.Closed Then
duz.Closed = True
End If
duz.Update

End Sub

Attribute VB_Name = "UserForm3"
Attribute VB_Base = "0{C2673CED-56C8-4C64-87AE-B1E30215F574}{71106CBF-E064-4F1F-BDB2-4CE0FFDFDA44}"
Attribute VB_GlobalNameSpace = False
Attribute VB_Creatable = False
Attribute VB_PredeclaredId = True
Attribute VB_Exposed = False
Attribute VB_TemplateDerived = False
Attribute VB_Customizable = False
Private Sub CommandButton1_Click()
 Dim i As Integer
    Dim ugao As Double
    Dim manji As Double
    Dim veci As Double
    Dim polarne(0 To 11) As Variant
    Dim centar(0 To 2) As Double
    Dim duz As AcadLine
    veci = 50
    
    manji = 25
    ugao = 0
    For i = 0 To 11
        If ugao Mod 90 = 0 Then
            polarne(i) = ThisDrawing.Utility.PolarPoint(centar, ugao * 3.14 / 180, veci)
        Else
            polarne(i) = ThisDrawing.Utility.PolarPoint(centar, ugao * 3.14 / 180, manji)
        End If
        If i Mod 3 = 0 Then
            ugao = ugao + 15
        ElseIf (ugao + 15) Mod 90 = 0 Then
            ugao = ugao + 15
        Else
            ugao = ugao + 60
        End If
        If i > 0 Then
            Set duz = ThisDrawing.ModelSpace.AddLine(polarne(i), polarne(i - 1))
            duz.Update
        End If
    Next
    Set duz = ThisDrawing.ModelSpace.AddLine(polarne(11), polarne(0))
    duz.Update

End Sub
